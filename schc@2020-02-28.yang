module schc{
    yang-version "1";
    namespace "urn:ietf:lpwan:schc:rules-description";
    prefix "schc";

    import schc-id {
        prefix "schc-id";
    }

    description
        "Generic Data model for Static Context Header Compression Rule for SCHC,
        based on draft-ietf-lpwan-ipv6-static-context-hc-18. Include compression
        rules and fragmentation rules.";

    revision 2020-02-28 {
        description "Add Fragmentation parameters";
    }

    revision 2020-01-23 {
        description "Modified TV with binary and union";
    }

    revision 2020-01-07 {
        description "First version of the YANG model";
    }


// --------  RULE DEFINITION ------------

    grouping target-values-struct {
        leaf value {
            type union {
                type binary;
                type string;
            }
        }
        leaf position {
            type uint16;
        }
    }

    grouping compression-rule-entry {
        leaf field-id {
            mandatory true;
            type schc-id:field-id-type;
        }
        leaf field-length {
            mandatory true;
            type schc-id:field-length-type;
        }
        leaf field-position {
            mandatory true;
            type uint8; 
        }
        leaf direction-indicator {
            mandatory true;
            type schc-id:direction-indicator-type;
        }
        list target-values {
            key position;
            uses target-values-struct;
        }
        leaf mo {
            mandatory true;
            type schc-id:matching-operator-type;
        }
        list mo-value {
            key position;
            uses target-values-struct;
        }
        leaf cda {
            mandatory true;
            type schc-id:comp-decomp-action-type;
        }
        list cda-value {
            key position;
            uses target-values-struct;
        }
    }

    grouping fragmentation-content {
        leaf direction {
            type schc-id:direction-indicator-type;
            description "should be up or down";
        }

        leaf dtagsize {
            type uint8;
            description "size in bit of the DTag field";
        }
        leaf wsize {
            type uint8;
            description "size in bit of the window field";
        }
        leaf fcnsize {
            type uint8;
            description "size in bit of the FCN field";
        }
        leaf RCS-algorithm {
            type RCS-algorithm-type;
            default schc-id:RFC8724-RCS;
            description "Algoritm used for RCS";
        }
        leaf maximum-window-size {
            type uint16;
            description "by default 2^wsize - 1";
        }

        leaf retransmission-timer {
            type uint64;
            description "duration in seconds of the retransmission timer"; // Check the units
        }

        leaf inactivity-timer {
            type uint64;
            description "duration is seconds of the inactivity timer"; // check units
        }

        leaf max-ack-requests {
            type uint8;        
        }

        leaf maximum-packet-size {
            type uint16;
            mandatory true;
            default 1280;
            description "When decompression is done, packet size must not strictly exceed this limit in Bytes";
        }

        choice mode {
            mandatory true;
            case no-ack;
            case ack-always;
            case ack-on-error {
                leaf tile-size {
                    type uint8;
                    description "size in bit of tiles";
                }
                leaf tile-in-All1 {
                    type boolean;
                    description "When true, sender and receiver except a tile in All-1 frag";
                }
                leaf ack-behavior {
                    type schc-id:ack-behavior-type;
                    mandatory true;
                }

            }
       }
    }

    grouping compression-content {
        list entry {
            key "field-id field-position direction-indicator"; 
            uses compression-rule-entry;
        }
    }

// Define rule ID. Rule ID is composed of a RuleID value and a Rule ID Length

    grouping rule-id-type {
        leaf rule-id {
            type uint32;
            description "rule ID value, this value must be unique combined with the length";
        }
        leaf rule-length {
            type uint8 {
                range 0..32;
            }
            description "rule ID length in bits, value 0 is for implicit rules";
        }
    }

// SCHC table for a specific device.

    container schc {
        leaf version{
            type uint64;
            mandatory false;
            description "used as an indication for versioning";
        }
        list rule {
            key "rule-id rule-length";
            uses rule-id-type;
            choice nature {
                case fragmentation {
                    uses fragmentation-content;
                }
                case compression {
                    uses compression-content;
                }
            }
        }
    }
  
  
}
